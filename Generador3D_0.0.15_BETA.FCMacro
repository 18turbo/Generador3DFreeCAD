# -*- coding: utf-8 -*-
# (c) 18Turbo, 2022

__Name__ = 'Generator3D'
__Comment__ = 'Create a solid with 2 or 3 sketches (views)'
__Author__ = '18Turbo'
__Version__ = '0.0.15'
__Date__ = '2022-08-30'
__License__ = 'LGPL-2.0-or-later'
__Web__ = 'https://github.com/18turbo/Generador3DFreeCAD'
__Wiki__ = 'https://github.com/18turbo/Generador3DFreeCAD/wiki'
__Icon__ = 'https://github.com/18turbo/Generador3DFreeCAD/blob/main/generador3D.svg'
__Help__ = ''
__Status__ = 'beta'
__Requires__ = 'FreeCAD >= v0.20'
__Contact__ = 'https://github.com/18turbo'
__Communication__ = 'https://github.com/18turbo/Generador3DFreeCAD/issues'
__Files__ = 'Generator3D.svg,Generator3D/Generator3D15.ui'


# (En español:)
# Funcionalidad:	Genera una pieza 3D a partir de 2 o 3 sketch, cada uno en una vista distinta (planta, frontal o lateral)
#
# Descripción:      Una vez ejecutada la macro, habrá que asociar cada sketch a cada vista, y pulsar el botón de OK.
#
#
# Notas de versiones:
# v.0.0.15:        Cambiada la interfaz
#                    Añadido el Offset y la longitud en cada vista
#                    El script funciona para las vistas inversas
# v.0.0.14:     Adaptación al Addon Manager
# v.0.0.13:     Depuración de código
# v.0.0.12:     Depuración de código
#               Posibilidad de crear una carpeta automáticamente donde meter las vistas y ocultarlas
# v.0.0.11:		Incluida tolerancia 3D para evitar problemas en los límites.
# v.0.0.10:		Corrección de errores en sketch negativos
# v.0.0.9:		Cambio de interfaz y corrección de errores. Beta funcional.
# v.0.0.8:		Corrección de errores
# v.0.0.7:		Corrección de errores
# v.0.0.6:		Primera versión BETA
# v.0.0.5 ALFA:	Genera la pieza 3D con 3 vistas
# v.0.0.4 ALFA:	Arregla la selección en las vistas en la pestaña Task (Tarea)
#
#
# BetaTester: Rafael García Rodríguez
# BetaTester: 18Turbo
 

import FreeCAD,FreeCADGui,Part

from PySide import QtCore, QtGui
from FreeCAD import Base


rutaMacro = FreeCAD.ParamGet("User parameter:BaseApp/Preferences/Macro")     
rutaUI = rutaMacro.GetString("MacroPath","") + "/generador3D/generador3D15.ui"
rutaUI = rutaUI.replace("\\","/")

class Generador3D:
    def __init__(self):
        self.form = FreeCADGui.PySideUic.loadUi(rutaUI)

        self.form.setWindowTitle("Generator 3D (Generador 3D)")

        lista = []
        self.nombrePlanta = ""
        self.nombreFrontal = ""
        self.nombreLateral = ""
        self.frontal = False
        self.lateral = False
        self.planta = False
        self.vistasActivas = 0

        for buscandoBocetos in objetos:
            if buscandoBocetos.TypeId.find('Sketcher::') > -1:
                lista.append(buscandoBocetos.Label)

        for i in lista:
            self.form.listWidgetFrontal.addItem(i)
            self.form.listWidgetLateral.addItem(i)
            self.form.listWidgetPlanta.addItem(i)

        self.form.listWidgetFrontal.itemSelectionChanged.connect(self.cambiaSeleccionFrontal)
        self.form.listWidgetLateral.itemSelectionChanged.connect(self.cambiaSeleccionLateral)
        self.form.listWidgetPlanta.itemSelectionChanged.connect(self.cambiaSeleccionPlanta)


    def cambiaSeleccionFrontal(self):
        self.nombreFrontal = str(self.form.listWidgetFrontal.selectedItems()[0].text())
        if not (self.frontal):
            self.frontal = True
            self.vistasActivas = self.vistasActivas + 1

    def cambiaSeleccionLateral(self):
        self.nombreLateral = str(self.form.listWidgetLateral.selectedItems()[0].text())
        if not (self.lateral):
            self.lateral = True
            self.vistasActivas = self.vistasActivas + 1

    def cambiaSeleccionPlanta(self):
        self.nombrePlanta = str(self.form.listWidgetPlanta.selectedItems()[0].text())
        if not (self.planta):
            self.planta = True
            self.vistasActivas = self.vistasActivas + 1

    def extrusion(self,nombreExtrusion,nombreEnVista,vista):
        App.ActiveDocument.addObject('Part::Extrusion',nombreExtrusion)
        f = App.ActiveDocument.getObject(nombreExtrusion)
        objf = App.ActiveDocument.getObjectsByLabel(nombreEnVista)
        f.Base = App.ActiveDocument.getObject(objf[0].Name)
        f.DirMode = "Custom"
        if vista == "planta":
            offset = self.form.offsetP.value()
            longitud = self.form.longP.value()
            f.Dir = App.Vector(0.000000000000000,0.000000000000000,1.000000000000000)
            if self.lateral:
               objetoLateral = App.ActiveDocument.getObjectsByLabel(self.nombreLateral)[0]
               maximoLZ = objetoLateral.Shape.BoundBox.ZMax
               minimoLZ = objetoLateral.Shape.BoundBox.ZMin
               if abs(maximoLZ) > abs(minimoLZ):
                   f.LengthFwd = (abs(maximoLZ) + self.form.tolerancia.value()) *2
               else:
                   f.LengthFwd = (abs(minimoLZ) + self.form.tolerancia.value()) *2
            else:
               objetoFrontal = App.ActiveDocument.getObjectsByLabel(self.nombreFrontal)[0]
               maximoFZ = objetoFrontal.Shape.BoundBox.ZMax
               minimoFZ = objetoFrontal.Shape.BoundBox.ZMin
               if abs(maximoFZ) > abs(minimoFZ):
                   f.LengthFwd = (abs(maximoFZ) + self.form.tolerancia.value()) *2
               else:
                   f.LengthFwd = (abs(minimoFZ) + self.form.tolerancia.value()) *2

        elif vista == "frontal":
            offset = self.form.offsetF.value()
            longitud = self.form.longF.value()
            f.Dir = App.Vector(0.000000000000000,1.000000000000000,0.000000000000000)
            if self.lateral:
                objetoLateral = App.ActiveDocument.getObjectsByLabel(self.nombreLateral)[0]
                maximoLY = objetoLateral.Shape.BoundBox.YMax
                minimoLY = objetoLateral.Shape.BoundBox.YMin
                if abs(maximoLY) > abs(minimoLY):
                    f.LengthFwd = (abs(maximoLY) + self.form.tolerancia.value()) *2
                else:
                    f.LengthFwd = (abs(minimoLY) + self.form.tolerancia.value()) *2
            else:
                objetoPlanta = App.ActiveDocument.getObjectsByLabel(self.nombrePlanta)[0]
                maximoPY = objetoPlanta.Shape.BoundBox.YMax
                minimoPY = objetoPlanta.Shape.BoundBox.YMin
                if abs(maximoPY) > abs(minimoPY):
                    f.LengthFwd = (abs(maximoPY) + self.form.tolerancia.value()) *2
                else:
                    f.LengthFwd = (abs(minimoPY) + self.form.tolerancia.value()) *2

        elif vista == "lateral":
            offset = self.form.offsetL.value()
            longitud = self.form.longL.value()
            f.Dir = App.Vector(1.000000000000000,0.000000000000000,0.000000000000000)
            if self.planta:
                objetoPlanta = App.ActiveDocument.getObjectsByLabel(self.nombrePlanta)[0]
                maximoPX = objetoPlanta.Shape.BoundBox.XMax
                minimoPX = objetoPlanta.Shape.BoundBox.XMin
                if abs(maximoPX) > abs(minimoPX):
                    f.LengthFwd = (abs(maximoPX) + self.form.tolerancia.value()) *2
                else:
                    f.LengthFwd = (abs(minimoPX) + self.form.tolerancia.value()) *2
            else:
                objetoFrontal = App.ActiveDocument.getObjectsByLabel(self.nombreFrontal)[0]
                maximoFX = objetoFrontal.Shape.BoundBox.XMax
                minimoFX = objetoFrontal.Shape.BoundBox.XMin
                if abs(maximoFX) > abs(minimoFX):
                    f.LengthFwd = (abs(maximoFX) + self.form.tolerancia.value()) *2
                else:
                    f.LengthFwd = (abs(minimoFX) + self.form.tolerancia.value()) *2

        f.DirLink = None        
        f.Solid = True
        f.Reversed = False
        if (offset>0) or (longitud>0):
            f.Symmetric = False
            f.LengthRev = offset * (-1)
            if (longitud>0):
                f.LengthFwd = longitud
        else:
            f.LengthRev = 0.000000000000000
            f.Symmetric = True
        f.TaperAngle = 0.000000000000000
        f.TaperAngleRev = 0.000000000000000
        App.ActiveDocument.recompute()
        return f

    def accept(self):
        #Comprobar que no existe ya una extrusión con este nombre
        numeroCoincidencias = 0
        encontradoCoincidencia = False
        cadenaAdicional = ""
        #objetos = FreeCAD.ActiveDocument.Objects
        for objeto in objetos:
            if ((objeto.Name.find('ExtrPlanta18Turbo') > -1) or 
               (objeto.Name.find('ExtrFrontal18Turbo') > -1) or
               (objeto.Name.find('ExtrLateral18Turbo') > -1)):
               numeroCoincidencias = numeroCoincidencias +1
               encontradoCoincidencia = True
        if encontradoCoincidencia:
            cadenaAdicional = cadenaAdicional + str(numeroCoincidencias)

        if (self.vistasActivas >= 2):
            if self.planta:
                # Sketch en Z (Planta XY)
                planta = self.extrusion("ExtrPlanta18Turbo" + cadenaAdicional,self.nombrePlanta,"planta")
            if self.frontal:
                # Sketch en Y (Frontal XZ)
                frontal = self.extrusion("ExtrFrontal18Turbo" + cadenaAdicional,self.nombreFrontal,"frontal")
            if self.lateral:
                # Sketch en X (Lateral YZ)
                lateral = self.extrusion("ExtrLateral18Turbo" + cadenaAdicional,self.nombreLateral,"lateral")

            # Intersección
            nombreInterseccion = "Pieza3D" + cadenaAdicional
            if (self.vistasActivas == 3):
                App.activeDocument().addObject("Part::MultiCommon",nombreInterseccion)
                App.ActiveDocument.getObject(nombreInterseccion).Shapes = [planta,frontal,lateral,]
            else:
                App.activeDocument().addObject("Part::MultiCommon",nombreInterseccion)
                if (self.planta) and (self.frontal):
                    App.ActiveDocument.getObject(nombreInterseccion).Shapes = [planta,frontal,]
                if (self.planta) and (self.lateral):
                   App.ActiveDocument.getObject(nombreInterseccion).Shapes = [planta,lateral,]
                if (self.frontal) and (self.lateral):
                   App.ActiveDocument.getObject(nombreInterseccion).Shapes = [frontal,lateral]
            App.ActiveDocument.recompute()

            #Meter vistas en Grupo (Carpeta)
            if self.form.meterVistasCarpeta.checkState():
                nombreGrupoVistas = 'VistasPieza3D' + cadenaAdicional
                App.activeDocument().Tip = App.activeDocument().addObject('App::DocumentObjectGroup',nombreGrupoVistas)
                if (self.planta):
                    objetoPlanta = App.ActiveDocument.getObjectsByLabel(self.nombrePlanta)[0]
                    App.ActiveDocument.getObject(nombreGrupoVistas).addObject(objetoPlanta)
                if (self.frontal):
                    objetoFrontal = App.ActiveDocument.getObjectsByLabel(self.nombreFrontal)[0]
                    App.ActiveDocument.getObject(nombreGrupoVistas).addObject(objetoFrontal)
                if (self.lateral):
                    objetoLateral = App.ActiveDocument.getObjectsByLabel(self.nombreLateral)[0]
                    App.ActiveDocument.getObject(nombreGrupoVistas).addObject(objetoLateral)
            #Ocultar Vistas
            if (self.planta):
                objetoPlanta.Visibility = False
            if (self.frontal):
                objetoFrontal.Visibility = False
            if (self.lateral):
                objetoLateral.Visibility = False

        FreeCADGui.Control.closeDialog()
 
objetos = FreeCAD.ActiveDocument.Objects       
panel = Generador3D()
FreeCADGui.Control.showDialog(panel)
